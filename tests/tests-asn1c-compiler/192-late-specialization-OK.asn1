-- OK: Everything is fine

-- iso.org.dod.internet.private.enterprise (1.3.6.1.4.1)
-- .spelio.software.asn1c.test (9363.1.5.1)
-- .192

-- A specialization that a later module creates (X.683 (02/2021) 9.7):
-- with -E -F -print-json, it gets the same processing as a specialization
-- that its own module creates (COMPONENTS OF, enumeration numbers, tags).
-- No -P reference: C code generation stops on this input (upstream).

ModuleLateSpecialization
	{ iso org(3) dod(6) internet(1) private(4) enterprise(1)
		spelio(9363) software(1) asn1c(5) test(1) 192 }
	DEFINITIONS AUTOMATIC TAGS ::=
BEGIN

	Base ::= SEQUENCE {
		id	INTEGER
	}

	Scoped {P} ::= SEQUENCE {
		COMPONENTS OF Base,
		kind	ENUMERATED { a, b, ... },
		p	P
	}

	Early ::= Scoped {BOOLEAN}

END

ModuleLateSpecializationUse
	{ iso org(3) dod(6) internet(1) private(4) enterprise(1)
		spelio(9363) software(1) asn1c(5) test(1) 192 1 }
	DEFINITIONS AUTOMATIC TAGS ::=
BEGIN

	IMPORTS Scoped FROM ModuleLateSpecialization;

	Late ::= Scoped {INTEGER}

END
