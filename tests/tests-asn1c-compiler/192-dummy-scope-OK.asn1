-- OK: Everything is fine

-- iso.org.dod.internet.private.enterprise (1.3.6.1.4.1)
-- .spelio.software.asn1c.test (9363.1.5.1)
-- .192

-- A DummyReference does not hide the identifiers of an Enumeration or a
-- NamedNumberList (X.683 (02/2021) 8.4 NOTE; X.680 (02/2021) 19.12, 20.11).
-- References to a parameterized assignment have actual parameters
-- (X.683 9.2), except in EXPORTS and IMPORTS (X.683 9.1).

ModuleDummyScope
	{ iso org(3) dod(6) internet(1) private(4) enterprise(1)
		spelio(9363) software(1) asn1c(5) test(1) 192 1 }
	DEFINITIONS AUTOMATIC TAGS ::=
BEGIN
	EXPORTS Pair;

	Color ::= ENUMERATED { red, green }
	Level ::= INTEGER { low(1), high(9) }
	Int ::= INTEGER (0..MAX)

	Paint {Int:red} ::= SEQUENCE {
		c	Color DEFAULT red,
		n	INTEGER (0..red)
	}

	Scale {Int:high} ::= SEQUENCE {
		l	Level DEFAULT high,
		m	INTEGER (0..high)
	}

	Pair {T} ::= SEQUENCE {
		first	T,
		second	BOOLEAN
	}
	Holder ::= OCTET STRING (CONTAINING Pair {INTEGER})

	Outer {U} ::= SEQUENCE {
		p	Pair {U},
		u	U
	}
	OuterInt ::= Outer {INTEGER}

END

ModuleDummyScopeImports
	{ iso org(3) dod(6) internet(1) private(4) enterprise(1)
		spelio(9363) software(1) asn1c(5) test(1) 192 2 }
	DEFINITIONS AUTOMATIC TAGS ::=
BEGIN
	IMPORTS Pair{} FROM ModuleDummyScope
		{ iso org(3) dod(6) internet(1) private(4) enterprise(1)
		spelio(9363) software(1) asn1c(5) test(1) 192 1 };

	PairBool ::= Pair {BOOLEAN}

END
