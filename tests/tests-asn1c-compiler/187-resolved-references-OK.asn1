-- OK: Everything is fine

-- iso.org.dod.internet.private.enterprise (1.3.6.1.4.1)
-- .spelio.software.asn1c.test (9363.1.5.1)
-- .187

-- Provenance and references in the tree after the fixer (asn1c -E -F -print-json):
-- COMPONENTS OF origin and stable ids, a union of contained subtypes with
-- partial WITH COMPONENTS (X.680 (02/2021) 51.3, 51.8.5), a DummyReference in
-- CONTAINING (X.683 (02/2021) 9.7), named numbers, an object set, and
-- component relations "@x" and "@.x" (X.682 (02/2021) 10.10).

ModuleResolvedReferences
	{ iso org(3) dod(6) internet(1) private(4) enterprise(1)
		spelio(9363) software(1) asn1c(5) test(1) 187 }
	DEFINITIONS AUTOMATIC TAGS ::=
BEGIN

	Common ::= SEQUENCE {
		stationId	INTEGER,
		kind		Kind
	}

	Kind ::= INTEGER { car(1), bus(2) } (0..255)

	Vehicle ::= SEQUENCE {
		COMPONENTS OF Common,
		speed	INTEGER,
		...
	}

	Base ::= SEQUENCE {
		type	Kind,
		plate	IA5String OPTIONAL,
		extra	NULL OPTIONAL
	}

	Car ::= Base (WITH COMPONENTS {..., type (car), plate PRESENT})
	Bus ::= Base (WITH COMPONENTS {..., type (bus), extra ABSENT})
	Road ::= Base (Car | Bus)

	Wrapped {Content} ::= SEQUENCE {
		data	OCTET STRING (CONTAINING Content)
	}

	WrappedCar ::= Wrapped {Car}

	CONTAINER ::= CLASS {
		&id	Kind UNIQUE,
		&Type
	} WITH SYNTAX { &Type IDENTIFIED BY &id }

	carId Kind ::= 1
	busId Kind ::= 2

	Containers CONTAINER ::= { {Car IDENTIFIED BY carId} | {Bus IDENTIFIED BY busId} }

	Message ::= SEQUENCE {
		id	CONTAINER.&id ({Containers}),
		body	CHOICE {
			value	CONTAINER.&Type ({Containers}{@.id}),
			none	NULL
		},
		copy	CONTAINER.&Type ({Containers}{@id})
	}

END
