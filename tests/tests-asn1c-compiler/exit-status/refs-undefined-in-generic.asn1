-- Semantic error for check-exit-status.sh (not scanned by check_fixer).
-- A parameterized type uses a name that no module defines. The fixer does
-- not resolve references inside a generic form; with -E -F -print-json the
-- reference pass shall report it.

ModuleRefsUndefinedGeneric
	{ iso org(3) dod(6) internet (1) private(4) enterprise(1)
		spelio(9363) software(1) asn1c(5) test(1) 187 1 }
	DEFINITIONS AUTOMATIC TAGS ::=
BEGIN
	Wrapper {P} ::= SEQUENCE { p P, u Undefined OPTIONAL }
END
