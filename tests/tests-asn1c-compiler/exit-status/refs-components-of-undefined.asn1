-- Semantic error for check-exit-status.sh (not scanned by check_fixer).
-- COMPONENTS OF an undefined type in a generic form.

ModuleRefsComponentsOfUndefined
	{ iso org(3) dod(6) internet (1) private(4) enterprise(1)
		spelio(9363) software(1) asn1c(5) test(1) 191 2 }
	DEFINITIONS AUTOMATIC TAGS ::=
BEGIN
	W {T} ::= SEQUENCE { COMPONENTS OF Nosuch, t T } (WITH COMPONENTS {..., b PRESENT})
END
