-- Semantic error for check-exit-status.sh (not scanned by check_fixer).
-- WITH COMPONENTS names a component that the type does not have
-- (X.680 (02/2021) 51.8.6), and a component relation names a component
-- that does not exist (X.682 (02/2021) 10.9).

ModuleRefsUnknownComponent
	{ iso org(3) dod(6) internet (1) private(4) enterprise(1)
		spelio(9363) software(1) asn1c(5) test(1) 187 4 }
	DEFINITIONS AUTOMATIC TAGS ::=
BEGIN
	Base ::= SEQUENCE { a INTEGER, b BOOLEAN OPTIONAL }
	Constrained ::= Base (WITH COMPONENTS {..., c PRESENT})

	OBJ ::= CLASS { &id INTEGER UNIQUE, &Type } WITH SYNTAX { &Type IDENTIFIED BY &id }
	Objs OBJ ::= { {INTEGER IDENTIFIED BY 1} }
	Message ::= SEQUENCE {
		id	OBJ.&id ({Objs}),
		value	OBJ.&Type ({Objs}{@.nosuch})
	}
END
