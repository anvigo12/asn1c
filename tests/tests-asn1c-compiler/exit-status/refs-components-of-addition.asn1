-- Semantic error for check-exit-status.sh (not scanned by check_fixer).
-- COMPONENTS OF gives the root components only (X.680 (02/2021) 25.5):
-- the extension addition c is not a component of W (51.8.6).

ModuleRefsComponentsOfAddition
	{ iso org(3) dod(6) internet (1) private(4) enterprise(1)
		spelio(9363) software(1) asn1c(5) test(1) 191 1 }
	DEFINITIONS AUTOMATIC TAGS ::=
BEGIN
	Base ::= SEQUENCE { a INTEGER, b BOOLEAN OPTIONAL, ..., c NULL OPTIONAL }
	W {T} ::= SEQUENCE { COMPONENTS OF Base, t T } (WITH COMPONENTS {..., c PRESENT})
END
