-- OK: Everything is fine

-- iso.org.dod.internet.private.enterprise (1.3.6.1.4.1)
-- .spelio.software.asn1c.test (9363.1.5.1)
-- .188

-- Nested actual parameters (X.683 (02/2021) 9): with -E -F -print-json, a
-- bound form keeps the actual parameters of an actual parameter
-- ("Inner {X}" in "Wrap {Inner {X}}"), and two uses with different nested
-- actual parameters give two bound forms.

ModuleNestedActualParameters
	{ iso org(3) dod(6) internet(1) private(4) enterprise(1)
		spelio(9363) software(1) asn1c(5) test(1) 188 }
	DEFINITIONS AUTOMATIC TAGS ::=
BEGIN

	Wrap {T} ::= SEQUENCE {
		v	T
	}

	Inner {Y} ::= SEQUENCE {
		y	Y
	}

	Outer {X} ::= Wrap {Inner {X}}

	UseInteger ::= Outer {INTEGER}
	UseBoolean ::= Outer {BOOLEAN}
	Direct ::= Wrap {Inner {NULL}}

END
