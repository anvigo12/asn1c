-- OK: Everything is fine

-- iso.org.dod.internet.private.enterprise (1.3.6.1.4.1)
-- .spelio.software.asn1c.test (9363.1.5.1)
-- .190

-- NULL as the actual parameter of a type parameter (X.683 (02/2021) 9.6):
-- the parser reads the word NULL as a value. Where the dummy reference is
-- a type, the specialization uses the NULL type.

ModuleNullActualParameter
	{ iso org(3) dod(6) internet(1) private(4) enterprise(1)
		spelio(9363) software(1) asn1c(5) test(1) 190 }
	DEFINITIONS AUTOMATIC TAGS ::=
BEGIN

	Inner {Y} ::= SEQUENCE {
		y	Y
	}

	Opt {Y} ::= SEQUENCE {
		y	Y OPTIONAL
	}

	WithNull ::= Inner {NULL}
	WithOptionalNull ::= Opt {NULL}

END
