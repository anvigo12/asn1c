-- OK: Everything is fine

-- iso.org.dod.internet.private.enterprise (1.3.6.1.4.1)
-- .spelio.software.asn1c.test (9363.1.5.1)
-- .193

-- An actual parameter that is a parameterized type reference with actual
-- parameters (X.683 (02/2021) 9.7): with -E -F -print-json, it names its
-- own specialization, also where the parameterized type uses its dummy
-- reference only inside CONSTRAINED BY.

ModuleActualParameterBoundForms
	{ iso org(3) dod(6) internet(1) private(4) enterprise(1)
		spelio(9363) software(1) asn1c(5) test(1) 193 }
	DEFINITIONS AUTOMATIC TAGS ::=
BEGIN

	Inner {P} ::= SEQUENCE {
		p	P
	}

	Opaque {T} ::= OCTET STRING (CONSTRAINED BY {
		-- the encoding of -- T
	})

	Twice {T} ::= Opaque {T}

	Use ::= Opaque {Inner {INTEGER}}

	Holder ::= SEQUENCE {
		v	Opaque {Inner {BOOLEAN}}
	}

	Nested ::= Twice {Inner {NULL}}

END
