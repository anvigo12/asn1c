-- OK: Everything is fine

-- iso.org.dod.internet.private.enterprise (1.3.6.1.4.1)
-- .spelio.software.asn1c.test (9363.1.5.1)
-- .191

-- A parameterized type reference with actual parameters inside a constraint
-- (X.683 (02/2021) 9.7): with -E -F -print-json, it names its own
-- specialization, also inside WITH COMPONENTS, inside a specialization, and
-- from another module. A specialization that is created after its
-- parameterized type was processed gets the same processing.

ModuleConstraintBoundForms
	{ iso org(3) dod(6) internet(1) private(4) enterprise(1)
		spelio(9363) software(1) asn1c(5) test(1) 191 }
	DEFINITIONS AUTOMATIC TAGS ::=
BEGIN

	Base ::= SEQUENCE {
		id	INTEGER
	}

	Scoped {P} ::= SEQUENCE {
		COMPONENTS OF Base,
		kind	ENUMERATED { a, b, ... },
		p	P
	}

	Outer ::= SEQUENCE {
		content	OCTET STRING
	}

	Wrap {T} ::= Outer (WITH COMPONENTS {
		content (CONTAINING T)
	})

	Direct ::= Outer (WITH COMPONENTS {
		content (CONTAINING Scoped {BOOLEAN})
	})

	Nested ::= Wrap {Scoped {INTEGER}}

END

ModuleConstraintBoundFormsUse
	{ iso org(3) dod(6) internet(1) private(4) enterprise(1)
		spelio(9363) software(1) asn1c(5) test(1) 191 1 }
	DEFINITIONS AUTOMATIC TAGS ::=
BEGIN

	IMPORTS Scoped, Outer FROM ModuleConstraintBoundForms;

	Imported ::= Outer (WITH COMPONENTS {
		content (CONTAINING Scoped {OCTET STRING})
	})

END
